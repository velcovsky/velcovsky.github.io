Attribute VB_Name = "Module1"
Public Sub Excel_test()

'nastaveni excel- zapnout tools_references_microsoft excel
'setup excel- chech if tools_references_microsoft excel is enable
Dim ExL As Excel.Application
Dim XlWorkBook As Excel.Workbook
Dim excelSheet As Excel.Worksheet

'kontrola musi byt nainstalovany excel
'chech if excel is instaled
On Error Resume Next
Set ExL = GetObject("", "Excel.Application")
ExL.Visible = True
If (Err.Number <> 0) Then
Err.Clear
MsgBox "You must have Excel loaded on your computer!"
Exit Sub
End If

'cesta k excel souboru a listu sesitu
'path, name and sheet of workbook
Set XlWorkBook = Workbooks.Open("C:\trans\TestFile.xlsx")
Sheets("List1").Select
Set excelSheet = ExL.ActiveWorkbook.Sheets("List1")

'zjisti cislo posledniho radku
'find number of last row
R$ = "222"
For I = 1 To 10
If excelSheet.Cells(I, 1).Value = "111" Then
excelSheet.Cells(I, 2).Value = "ttt"
I = 11 'break out of the loop
End If
Next I


'zapis do bunek
'edit cells
'excelSheet.Cells(4, 6).Value = "test25"

'ulozit a zavrit~~~~~~~~~~~~~~~~~~'
'save and close~~~~~~~~~~~~~~~~~~~'
'ExL.ScreenUpdating = True
XlWorkBook.Save
XlWorkBook.Close
ExL.Application.Quit
'Set ExL = Nothing
'Set XlWorkBook = Nothing
'Set excelSheet = Nothing

End Sub
