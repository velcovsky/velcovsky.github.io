Attribute VB_Name = "Module1"
Sub Black_SetWindowToPlot()

    'testovaci verze !!!!


    ' This example allows the user to define an area in the current layout
    ' and displays a plot preview of the defined area.
    '
    ' * Note: You have to exit the
    ' plot preview before the VBA example will stop and control will be returned

    AppActivate ThisDrawing.Application.Caption

    Dim point1 As Variant, point2 As Variant
    
    ' Get first point in window
    point1 = ThisDrawing.Utility.GetPoint(, "Click the lower-left of the window to plot.")
    ReDim Preserve point1(0 To 1)   ' Change this to a 2D array by removing the Z position
    
    ' Get second point in window
    point2 = ThisDrawing.Utility.GetPoint(, "Click the upper-right of the window to plot.")
    ReDim Preserve point2(0 To 1)   ' Change this to a 2D array by removing the Z position
    
    ' Send information about window to current layout
    ThisDrawing.ActiveLayout.SetWindowToPlot point1, point2
    
    ' Read back window information
    ThisDrawing.ActiveLayout.GetWindowToPlot point1, point2
    
    'MsgBox "Press any key to plot the following window:" & vbCrLf & vbCrLf & _
          ' "Lower Left: " & point1(0) & ", " & point1(1) & vbCrLf & _
          ' "Upper Right: " & point2(0) & ", " & point2(1)
          
    '----------------------------------------
    ' added by RICVBA
    Dim point1w(0 To 2) As Double
    Dim point2w(0 To 2) As Double
    point1w(0) = point1(0): point1w(1) = point1(1): point1w(2) = 0
    point2w(0) = point2(0): point2w(1) = point2(1): point2w(2) = 0
    ZoomWindow point1w, point2w ' make the current display fit the "window to plot"
    '----------------------------------------
    
    ' Plot the current display
    'ThisDrawing.ActiveLayout.ConfigName = "DWG to PDF.pc3"
    'ThisDrawing.ActiveLayout.PlotType = acDisplay ' <--- revised by RICVBA
    'ThisDrawing.ActiveLayout.PlotType = acWindow ' <--- revised by RICVBA
    'ThisDrawing.ActiveLayout.CenterPlot = True ' <--- added by RICVBA
    'ThisDrawing.ActiveLayout.StandardScale = acScaleToFit ' <--- added by RICVBA
    'ThisDrawing.Plot.DisplayPlotPreview acFullPreview
    
    ThisDrawing.ActiveLayout.GetWindowToPlot point1, point2
    ThisDrawing.ActiveLayout.ConfigName = "DWG to PDF.pc3"
    ThisDrawing.ActiveLayout.StyleSheet = "monochrome.ctb"
    ThisDrawing.ActiveLayout.PlotRotation = ac90degrees
    ThisDrawing.ActiveLayout.CenterPlot = True
    ThisDrawing.ActiveLayout.StandardScale = acScaleToFit
    ThisDrawing.ActiveLayout.PlotType = acWindow
    ThisDrawing.ActiveLayout.ConfigName = "DWG to PDF.pc3"
    ThisDrawing.ActiveLayout.CanonicalMediaName = "ISO_full_bleed_A3_(297.00_x_420.00_MM)"
    
    ThisDrawing.Plot.PlotToDevice
    
    ZoomPrevious ' restore the previous zoom (optional) ' <--- added by RICVBA
    
End Sub

Attribute VB_Name = "Module2"
Sub Colour_SetWindowToPlot()

    'testovaci verze !!!!


    ' This example allows the user to define an area in the current layout
    ' and displays a plot preview of the defined area.
    '
    ' * Note: You have to exit the
    ' plot preview before the VBA example will stop and control will be returned

    AppActivate ThisDrawing.Application.Caption

    Dim point1 As Variant, point2 As Variant
    
    ' Get first point in window
    point1 = ThisDrawing.Utility.GetPoint(, "Click the lower-left of the window to plot.")
    ReDim Preserve point1(0 To 1)   ' Change this to a 2D array by removing the Z position
    
    ' Get second point in window
    point2 = ThisDrawing.Utility.GetPoint(, "Click the upper-right of the window to plot.")
    ReDim Preserve point2(0 To 1)   ' Change this to a 2D array by removing the Z position
    
    ' Send information about window to current layout
    ThisDrawing.ActiveLayout.SetWindowToPlot point1, point2
    
    ' Read back window information
    ThisDrawing.ActiveLayout.GetWindowToPlot point1, point2
    
    'MsgBox "Press any key to plot the following window:" & vbCrLf & vbCrLf & _
          ' "Lower Left: " & point1(0) & ", " & point1(1) & vbCrLf & _
          ' "Upper Right: " & point2(0) & ", " & point2(1)
          
    '----------------------------------------
    ' added by RICVBA
    Dim point1w(0 To 2) As Double
    Dim point2w(0 To 2) As Double
    point1w(0) = point1(0): point1w(1) = point1(1): point1w(2) = 0
    point2w(0) = point2(0): point2w(1) = point2(1): point2w(2) = 0
    ZoomWindow point1w, point2w ' make the current display fit the "window to plot"
    '----------------------------------------
    
    ' Plot the current display
    'ThisDrawing.ActiveLayout.ConfigName = "DWG to PDF.pc3"
    'ThisDrawing.ActiveLayout.PlotType = acDisplay ' <--- revised by RICVBA
    'ThisDrawing.ActiveLayout.PlotType = acWindow ' <--- revised by RICVBA
    'ThisDrawing.ActiveLayout.CenterPlot = True ' <--- added by RICVBA
    'ThisDrawing.ActiveLayout.StandardScale = acScaleToFit ' <--- added by RICVBA
    'ThisDrawing.Plot.DisplayPlotPreview acFullPreview
    
    ThisDrawing.ActiveLayout.GetWindowToPlot point1, point2
    ThisDrawing.ActiveLayout.ConfigName = "DWG to PDF.pc3"
    ThisDrawing.ActiveLayout.StyleSheet = "fill patterns.ctb"
    ThisDrawing.ActiveLayout.PlotRotation = ac90degrees
    ThisDrawing.ActiveLayout.CenterPlot = True
    ThisDrawing.ActiveLayout.StandardScale = acScaleToFit
    ThisDrawing.ActiveLayout.PlotType = acWindow
    ThisDrawing.ActiveLayout.ConfigName = "DWG to PDF.pc3"
    ThisDrawing.ActiveLayout.CanonicalMediaName = "ISO_full_bleed_A3_(297.00_x_420.00_MM)"
    
    ThisDrawing.Plot.PlotToDevice
    
    ZoomPrevious ' restore the previous zoom (optional) ' <--- added by RICVBA
    
End Sub

Attribute VB_Name = "Module3"
Public Sub Vykresy_excel_test()

'nastaveni excel- zapnout tools_references_microsoft excel
'setup excel- chech if tools_references_microsoft excel is enable
Dim ExL As Excel.Application
Dim XlWorkBook As Excel.Workbook
Dim excelSheet As Excel.Worksheet

'kontrola musi byt nainstalovany excel
'chech if excel is instaled
On Error Resume Next
Set ExL = GetObject("", "Excel.Application")
ExL.Visible = True
If (Err.Number <> 0) Then
Err.Clear
MsgBox "You must have Excel loaded on your computer!"
Exit Sub
End If

'cesta k excel souboru a listu sesitu
'path, name and sheet of workbook
Set XlWorkBook = Workbooks.Open("C:\trans\TestFile.xlsx")
Sheets("List1").Select
Set excelSheet = ExL.ActiveWorkbook.Sheets("List1")

'najdi prvni prazdny radek - nefunguje
'find first empty row - not work
'Dim i As Long
'i = Cells(Rows.Count, 1).End(xlUp).Offset(1, 0).Select

'najdi prvni prazdny radek
'find first empty row
Dim Fnd As Excel.Range
Set Fnd = excelSheet.Range("A1:A1000").Find("")
R$ = Fnd.Address
Rw = Val(Mid$(R$, 4))
'Resulting_Value = excelSheet.Cells(Rw, 2).Value

'zapis do bunek
'edit cells
'excelSheet.Cells(Rw, 1).Value = "test29"


' najde blok - Rohové razítko Aquarex - zapise hodnoty do <Číslo_výkresu>, <Název_výkresu>, <Datum vytvoření>, <Autor>
' SEARCH BLOCK ON DRAWING.

Dim DrNumber_kpl As String '<Číslo_výkresu> - \W0.7500;xxxxxx
Dim DrNumber As String  '<Číslo_výkresu> editovane

Dim DrName_kpl As String '<Název_výkresu>
Dim DrName As String '<Název_výkresu> edit

Dim CrDate_kpl As String '<Datum vytvoření>
Dim CrDate As String '<Datum vytvoření> edit

Dim Autor_kpl As String '<Autor>
Dim Autor As String '<Autor> edit

For Each ENTITY In ThisDrawing.ModelSpace                                                   '  For eache entity inside modele space
    If ENTITY.ObjectName = "AcDbBlockReference" Then                                        '
        If ENTITY.EffectiveName = "Rohová razítka Aquarex" Or ENTITY.EffectiveName = "block name 2" Then  ' check block name inside the dwg
            If ENTITY.HasAttributes = True Then                                             ' Se il blocco ha attributi
                ATTRIB_LIST = ENTITY.GetAttributes                                          ' GET THE ARRAY "ATTRIB_LIST"
                INS_POINT = ENTITY.InsertionPoint                                           ' BLOCK INSERTION POINT
            'excelSheet.Cells(Rw, 1) = ENTITY.Name                                  ' BLOCK NAME
                    'excelSheet.Cells(Rw, 2) = ENTITY.Layer                         ' BLOCK LAYER
                    'excelSheet.Cells(Rw, 3) = ENTITY.EffectiveName                  ' BLOCK EFFECTIVE NAME
                    'excelSheet.Cells(Rw, 4) = INS_POINT(0)                  ' BLOCK INSERTION POINT X
                    'excelSheet.Cells(Rw, 5) = INS_POINT(1)                      ' BLOCK INSERTION POINT Y
                    'excelSheet.Cells(Rw, 6) = INS_POINT(2)                  ' BLOCK INSERTION POINT Z
                    'excelSheet.Cells(Rw, 1) = ATTRIB_LIST(9).TextString             ' WRITE ON EXCEL ATTRIBUTE VALUE <Číslo_výkresu>
                    'excelSheet.Cells(Rw, 2) = ATTRIB_LIST(0).TextString             ' WRITE ON EXCEL ATTRIBUTE VALUE <Název_výkresu>
                    'excelSheet.Cells(Rw, 3) = ATTRIB_LIST(11).TextString            ' WRITE ON EXCEL ATTRIBUTE VALUE <Datum vytvoření>
                    'excelSheet.Cells(Rw, 4) = ATTRIB_LIST(1).TextString            ' WRITE ON EXCEL ATTRIBUTE VALUE <Autor>
                    DrNumber_kpl = ATTRIB_LIST(9).TextString             ' WRITE ON EXCEL ATTRIBUTE VALUE <Číslo_výkresu>
                    DrName_kpl = ATTRIB_LIST(0).TextString             ' WRITE ON EXCEL ATTRIBUTE VALUE <Název_výkresu>
                    CrDate_kpl = ATTRIB_LIST(11).TextString            ' WRITE ON EXCEL ATTRIBUTE VALUE <Datum vytvoření>
                    Autor_kpl = ATTRIB_LIST(1).TextString            ' WRITE ON EXCEL ATTRIBUTE VALUE <Autor>
                    'ExRow = ExRow + 1
                    'i = i + 1
                End If
            End If
        End If
        
'editace textu ( odstrani "\W0.7500;")
'edit text ( remove "\W0.7500;")
DrNumber = Replace(DrNumber_kpl, "\W0.7500;", "")
DrName = Replace(DrName_kpl, "\W0.7500;", "")
CrDate = Replace(CrDate_kpl, "\W0.7500;", "")
Autor = Replace(Autor_kpl, "\W0.7500;", "")


'zapise hodnoty do bunek v excelu
' put text value in excel
excelSheet.Cells(Rw, 1) = DrNumber
excelSheet.Cells(Rw, 2) = DrName
excelSheet.Cells(Rw, 3) = CrDate
excelSheet.Cells(Rw, 4) = Autor


'Najde a nahradi(vymaze) prebytecne casti textu (atributu)
'Find and replace unnecessary part of attributs
'Dim MyRange As Range
'Sheets("List1").UsedRange.Replace What:="\W0.7500;", Replacement:=""

'ulozit a zavrit~~~~~~~~~~~~~~~~~~'
'save and close~~~~~~~~~~~~~~~~~~~'
XlWorkBook.Save
XlWorkBook.Close
Next

'ulozit a zavrit~~~~~~~~~~~~~~~~~~'
'save and close~~~~~~~~~~~~~~~~~~~'
'ExL.ScreenUpdating = True
'XlWorkBook.Save
'XlWorkBook.Close
ExL.Application.Quit
'Set ExL = Nothing
'Set XlWorkBook = Nothing
'Set excelSheet = Nothing

'show message  - first empty row
'MsgBox Rw

End Sub

Attribute VB_Name = "Module4"
Option Explicit
' Requires:
' Microsoft Excel Object Library
' go to Tools->Options->General Tab and check 'Break on Unhandled Errors'

Const xlFileName As String = "C:\trans\TestFile.xlsx" '<--change existing file name here

'~~~~~~~~~~~~~~~~~~~~~~~~~~~~~~~~~'
Public Sub ExportText()

Dim oSset As AcadSelectionSet
Dim oEnt As AcadEntity
Dim oText As acadText
Dim i As Long

Dim ftype(0) As Integer
Dim fdata(0) As Variant
ftype(0) = 0: fdata(0) = "TEXT"

Dim dxftype As Variant
Dim dxfdata As Variant

dxftype = ftype
dxfdata = fdata
'~~~~~~~~~~~~~~~~~~~~~~~~~~~~~~~~~'
Dim xlApp As Object

Dim xlBook As Object

Dim xlSheet As Object
Dim lngRow As Long, lngCol As Long
'~~~~~~~~~~~~~~~~~~~~~~~~~~~~~~~~~'
On Error Resume Next
Set xlApp = GetObject(, "Excel.Application")
If Err <> 0 Then
Err.Clear
Set xlApp = CreateObject("Excel.Application")
If Err <> 0 Then
MsgBox "Impossible to run Excel.", vbExclamation
End
End If
End If
'~~~~~~~~~~~~~~~~~~~~~~~~~~~~~~~~~'
On Error GoTo Err_Control

         With ThisDrawing.SelectionSets
              While .Count > 0
                   .Item(0).Delete
              Wend
         Set oSset = .Add("$Texts$")
         End With
oSset.SelectOnScreen dxftype, dxfdata
'~~~~~~~~~~~~~~~~~~~~~~~~~~~~~~~~~'
xlApp.Visible = True
Set xlBook = xlApp.Workbooks.Open(xlFileName)
Set xlSheet = xlBook.Sheets(1)
xlApp.ScreenUpdating = False
'~~~~~~~~~~~~~~~~~~~~~~~~~~~~~~~~~'
' xlSheet.Range("A1:A10").Find("").Select
' Range("A" & Rows.Count).End(xlUp).Offset(1).Select


lngRow = 3: lngCol = 1
For Each oEnt In oSset
Set oText = oEnt
xlSheet.Cells(lngRow, lngCol).Value = oText.TextString
lngCol = lngCol + 1
Next oEnt
'~~~~~~~~~~~~~~~~~~~~~~~~~~~~~~~~~'
'xlSheet.Columns.HorizontalAlignment = xlLeft
'xlSheet.Columns.AutoFit
'xlSheet.Cells(1, 6).value = "module6"

xlApp.ScreenUpdating = True

xlBook.Save
xlBook.Close
'~~~~~~~~~~~~~~~~~~~~~~~~~~~~~~~~~'
xlApp.Application.Quit
Set xlApp = Nothing
Set xlBook = Nothing
Set xlSheet = Nothing
'~~~~~~~~~~~~~~~~~~~~~~~~~~~~~~~~~'
MsgBox "Done"
'~~~~~~~~~~~~~~~~~~~~~~~~~~~~~~~~~'
Err_Control:
If Err.Number <> 0 Then
MsgBox Err.Description
End If

End Sub
'~~~~~~~~~~~~~~~~~~~~~~~~~~~~~~~~~'

Attribute VB_Name = "Module5"
Option Explicit
'cte z bloku atributy a zobrazi text
Public Sub GetAttributeValue()

    Dim ent As AcadEntity
    Dim blk As AcadBlockReference
    Dim i As Integer
    Dim pt As Variant
    
    ThisDrawing.Utility.GetEntity ent, pt, vbCr & "Select a block:"

    If ent Is Nothing Then Exit Sub
    If Not TypeOf ent Is AcadBlockReference Then Exit Sub
    
    Set blk = ent
    'Set blk = "Rohová razítka Aqurex"
    If Not blk.HasAttributes Then Exit Sub
    
    Dim atts As Variant
    Dim att As AcadAttributeReference
    
    atts = blk.GetAttributes()
    
    For i = 0 To UBound(atts)
    
       Set att = atts(i)
       MsgBox "Tag: " & att.TagString & vbCrLf & "Value: " & att.TextString

    Next

End Sub

Attribute VB_Name = "Module6"
Option Explicit
' Requires:
' Microsoft Excel Object Library
' go to Tools->Options->General Tab and check 'Break on Unhandled Errors'

Const xlFileName As String = "C:\trans\TestFile.xlsx" '<--change existing file name here

'~~~~~~~~~~~~~~~~~~~~~~~~~~~~~~~~~'
Public Sub ExportText()

Dim oSset As AcadSelectionSet
Dim oEnt As AcadEntity
Dim oText As acadText


Dim xlApp As Object
Dim xlBook As Object
Dim xlSheet As Object
Dim lngRow As Long, lngCol As Long
'~~~~~~~~~~~~~~~~~~~~~~~~~~~~~~~~~'
On Error Resume Next
Set xlApp = GetObject(, "Excel.Application")
If Err <> 0 Then
Err.Clear
Set xlApp = CreateObject("Excel.Application")
If Err <> 0 Then
MsgBox "Impossible to run Excel.", vbExclamation
End
End If
End If

xlApp.Visible = True
Set xlBook = xlApp.Workbooks.Open(xlFileName)
Set xlSheet = xlBook.Sheets(1)
xlApp.ScreenUpdating = False
Dim i As Long
'Dim Fnd As Excel.Range
Dim Fnd As String
Set Fnd = xlSheet.Range("A1:A10").Find("")
'R$ = Fnd.Address
'Rw = Val(Mid$(Fnd.Address, 4))
i = xlSheet.Cells(Val(Mid$(Fnd.Address, 4)), 2).Value
Dim i As Long
'i = xlSheet.Cells(Rows.Count, 1).End(xlUp).Row
'i = 8
'Fnd = xlSheet.Cells(Rows.Count, 1).End(xlDown).Row

xlSheet.Cells(i + 1, 1).Value = "module6"

xlApp.ScreenUpdating = True

xlBook.Save
xlBook.Close
'~~~~~~~~~~~~~~~~~~~~~~~~~~~~~~~~~'
xlApp.Application.Quit
Set xlApp = Nothing
Set xlBook = Nothing
Set xlSheet = Nothing
'~~~~~~~~~~~~~~~~~~~~~~~~~~~~~~~~~'
MsgBox "Done"
'~~~~~~~~~~~~~~~~~~~~~~~~~~~~~~~~~'
Err_Control:
If Err.Number <> 0 Then
MsgBox Err.Description
End If

End Sub
'~~~~~~~~~~~~~~~~~~~~~~~~~~~~~~~~~'

Attribute VB_Name = "Module7"
Sub ViewAttribs()
Dim E1 As Object
Dim ATS As Variant
Dim EA As AcadAttributeReference
Dim MS As AcadModelSpace
Set MS = ThisDrawing.ModelSpace
i = MS.Count - 1
For J = 0 To i
Set E1 = MS.Item(J)
If E1.EntityType = acBlockReference Then
ATS = E1.GetAttributes (<Název_výkresu>)
K = UBound(ATS) + 1
If K > 0 Then
S$ = "Found block - " & E1.Name & _
" - with " & Str$(K) & " attributes { "
For L = 0 To K - 1
Set EA = ATS(L)
S$ = S$ + EA.TagString & "/" & EA.TextString & " "
Next L
S$ = S$ & "}"
MsgBox S$
End If
End If
Next J
End Sub

Attribute VB_Name = "Module8"
Public Sub text()

Dim text As String
Dim edit_text As String

text = "1111_22021"
edit_text = Replace(text, "1111_", "")

MsgBox edit_text


End Sub
