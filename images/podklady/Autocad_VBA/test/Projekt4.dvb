Attribute VB_Name = "Module1"
Public Sub Vykresy_excel_test()

'nastaveni excel- zapnout tools_references_microsoft excel
'setup excel- chech if tools_references_microsoft excel is enable
Dim ExL As Excel.Application
Dim XlWorkBook As Excel.Workbook
Dim excelSheet As Excel.Worksheet

'kontrola musi byt nainstalovany excel
'chech if excel is instaled
On Error Resume Next
Set ExL = GetObject("", "Excel.Application")
ExL.Visible = True
If (Err.Number <> 0) Then
Err.Clear
MsgBox "You must have Excel loaded on your computer!"
Exit Sub
End If

'cesta k excel souboru a listu sesitu
'path, name and sheet of workbook
Set XlWorkBook = Workbooks.Open("C:\trans\TestFile.xlsx")
Sheets("List1").Select
Set excelSheet = ExL.ActiveWorkbook.Sheets("List1")

'najdi prvni prazdny radek - nefunguje
'find first empty row - not work
'Dim i As Long
'i = Cells(Rows.Count, 1).End(xlUp).Offset(1, 0).Select

'najdi prvni prazdny radek
'find first empty row
Dim Fnd As Excel.Range
Set Fnd = excelSheet.Range("A1:A1000").Find("")
R$ = Fnd.Address
Rw = Val(Mid$(R$, 4))
'Resulting_Value = excelSheet.Cells(Rw, 2).Value

'zapis do bunek
'edit cells
'excelSheet.Cells(Rw, 1).Value = "test29"


' najde blok - Rohové razítko Aquarex - zapise hodnoty do bunek
' SEARCH BLOCK ON DRAWING.
For Each ENTITY In ThisDrawing.ModelSpace                                                   '  For eache entity inside modele space
    If ENTITY.ObjectName = "AcDbBlockReference" Then                                        '
        If ENTITY.EffectiveName = "Rohová razítka Aquarex" Or ENTITY.EffectiveName = "block name 2" Then  ' check block name inside the dwg
            If ENTITY.HasAttributes = True Then                                             ' Se il blocco ha attributi
                ATTRIB_LIST = ENTITY.GetAttributes                                          ' GET THE ARRAY "ATTRIB_LIST"
                INS_POINT = ENTITY.InsertionPoint                                           ' BLOCK INSERTION POINT
            'excelSheet.Cells(Rw, 1) = ENTITY.Name                                  ' BLOCK NAME
                    'excelSheet.Cells(Rw, 2) = ENTITY.Layer                         ' BLOCK LAYER
                    'excelSheet.Cells(Rw, 3) = ENTITY.EffectiveName                  ' BLOCK EFFECTIVE NAME
                    'excelSheet.Cells(Rw, 4) = INS_POINT(0)                  ' BLOCK INSERTION POINT X
                    'excelSheet.Cells(Rw, 5) = INS_POINT(1)                      ' BLOCK INSERTION POINT Y
                    'excelSheet.Cells(Rw, 6) = INS_POINT(2)                  ' BLOCK INSERTION POINT Z
                    excelSheet.Cells(Rw, 1) = ATTRIB_LIST(9).TextString             ' WRITE ON EXCEL ATTRIBUTE VALUE <Název_výkresu>
                    excelSheet.Cells(Rw, 2) = ATTRIB_LIST(0).TextString             ' WRITE ON EXCEL ATTRIBUTE VALUE <Číslo_výkresu>
                    excelSheet.Cells(Rw, 3) = ATTRIB_LIST(11).TextString            ' WRITE ON EXCEL ATTRIBUTE VALUE <Datum vytvoření>
                    excelSheet.Cells(Rw, 4) = ATTRIB_LIST(1).TextString            ' WRITE ON EXCEL ATTRIBUTE VALUE <Autor>
                    'ExRow = ExRow + 1
                    'i = i + 1
                End If
            End If
        End If
        
'Najde a nahradi(vymaze) prebytecne casti textu (atributu)
'Find and replace unnecessary part of attributs
Dim MyRange As Range
Sheets("List1").UsedRange.Replace What:="\W0.7500;", Replacement:=""

'ulozit a zavrit~~~~~~~~~~~~~~~~~~'
'save and close~~~~~~~~~~~~~~~~~~~'
XlWorkBook.Save
XlWorkBook.Close
Next

'ulozit a zavrit~~~~~~~~~~~~~~~~~~'
'save and close~~~~~~~~~~~~~~~~~~~'
'ExL.ScreenUpdating = True
'XlWorkBook.Save
'XlWorkBook.Close
ExL.Application.Quit
'Set ExL = Nothing
'Set XlWorkBook = Nothing
'Set excelSheet = Nothing

'show message  - first empty row
'MsgBox Rw

End Sub

Attribute VB_Name = "Module2"
Sub TestFind()

'nastaveni excel- zapnout tools_references_microsoft excel
'setup excel- chech if tools_references_microsoft excel is enable
Dim ExL As Excel.Application
Dim XlWorkBook As Excel.Workbook
Dim excelSheet As Excel.Worksheet

'kontrola musi byt nainstalovany excel
'chech if excel is instaled
On Error Resume Next
Set ExL = GetObject("", "Excel.Application")
ExL.Visible = True
If (Err.Number <> 0) Then
Err.Clear
MsgBox "You must have Excel loaded on your computer!"
Exit Sub
End If

'cesta k excel souboru a listu sesitu
'path, name and sheet of workbook
Set XlWorkBook = Workbooks.Open("C:\trans\TestFile.xlsx")
Sheets("List1").Select
Set excelSheet = ExL.ActiveWorkbook.Sheets("List1")

Dim MyRange As Range
 
Sheets("List1").UsedRange.Replace What:="\W0.7500;", Replacement:=""


'MsgBox MyRange.Address
'MsgBox MyRange.Column
'MsgBox MyRange.Row

XlWorkBook.Save
XlWorkBook.Close


'ulozit a zavrit~~~~~~~~~~~~~~~~~~'
'save and close~~~~~~~~~~~~~~~~~~~'
'ExL.ScreenUpdating = True
'XlWorkBook.Save
'XlWorkBook.Close
ExL.Application.Quit
 
End Sub
