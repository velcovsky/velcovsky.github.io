Attribute VB_Name = "Module1"
Option Explicit

Sub Export()

    On Error GoTo ErrorHandler

    If Not Dir("C:\Users\" & Environ$("Username") & "\Documents\RESUME.XLW") = "" Then Kill ("C:\Users\" & Environ$("Username") & "\Documents\RESUME.XLW")
    
    Dim oExcel As Object
    Dim oBook As Object
    Dim oSheet As Object

    'Start a new workbook in Excel
    Set oExcel = CreateObject("Excel.Application")
    Set oBook = oExcel.Workbooks.Add
    Set oSheet = oBook.Worksheets(1)
    
    If Not Dir("C:\trans\Beam Locations.xlsx") = "" Then Kill ("C:\trans\Beam Locations.xlsx")
    
    'Save the Workbook and Quit Excel
    oBook.SaveAs "C:\trans\Beam Locations.xlsx"
    
    'Call SortDims("C:\trans\Beam Locations.xlsx", oExcel, oBook, oSheet)
    
    oExcel.Save
    oExcel.Quit
    
    Set oSheet = Nothing
    Set oBook = Nothing
    Set oExcel = Nothing
    
'\\\\\\\\\\\\\\\\\\\\\\\\\\\\\\\\\\\\\\\\\\\\\\\\\\\\\\\\\\\\\\\\\\\\\\\\\\\\\\\\\\\\\\\
ErrorHandler:
    If Err.Number = -2147352567 Then
    
        oExcel.Save
        oExcel.Quit
    
        Set oSheet = Nothing
        Set oBook = Nothing
        Set oExcel = Nothing
    
        Exit Sub
    End If
'\\\\\\\\\\\\\\\\\\\\\\\\\\\\\\\\\\\\\\\\\\\\\\\\\\\\\\\\\\\\\\\\\\\\\\\\\\\\\\\\\\\\\\\\
    
End Sub
