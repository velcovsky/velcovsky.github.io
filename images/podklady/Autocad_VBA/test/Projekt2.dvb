Attribute VB_Name = "Module1"
Public Sub Vykresy_excel_test()

'nastaveni excel- zapnout tools_references_microsoft excel
'setup excel- chech if tools_references_microsoft excel is enable
Dim ExL As Excel.Application
Dim XlWorkBook As Excel.Workbook
Dim excelSheet As Excel.Worksheet

'kontrola musi byt nainstalovany excel
'chech if excel is instaled
On Error Resume Next
Set ExL = GetObject("", "Excel.Application")
ExL.Visible = True
If (Err.Number <> 0) Then
Err.Clear
MsgBox "You must have Excel loaded on your computer!"
Exit Sub
End If

'cesta k excel souboru a listu sesitu
'path, name and sheet of workbook
Set XlWorkBook = Workbooks.Open("C:\trans\TestFile.xlsx")
Sheets("List1").Select
Set excelSheet = ExL.ActiveWorkbook.Sheets("List1")

'najdi prvni prazdny radek - nefunguje
'find first empty row - not work
'Dim i As Long
'i = Cells(Rows.Count, 1).End(xlUp).Offset(1, 0).Select

'najdi prvni prazdny radek
'find first empty row
Dim Fnd As Excel.Range
Set Fnd = excelSheet.Range("A1:A1000").Find("")
R$ = Fnd.Address
Rw = Val(Mid$(R$, 4))
'Resulting_Value = excelSheet.Cells(Rw, 2).Value

'zapis do bunek
'edit cells
excelSheet.Cells(Rw, 1).Value = "christmas mirac´le"

'ulozit a zavrit~~~~~~~~~~~~~~~~~~'
'save and close~~~~~~~~~~~~~~~~~~~'
'ExL.ScreenUpdating = True
XlWorkBook.Save
XlWorkBook.Close
ExL.Application.Quit
'Set ExL = Nothing
'Set XlWorkBook = Nothing
'Set excelSheet = Nothing

'show message  - first empty row
'MsgBox Rw

End Sub
