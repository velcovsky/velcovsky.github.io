Attribute VB_Name = "Module1"
Public Sub test()

End Sub

Dim ent As AcadEntity

Dim blk As AcadBlockReference

Dim pt As Variant

Dim i As Integer

Do

    ''Pick block reference

    ThisDrawing.Utility.GetEntity ent, pt, vbCr & "Pick a block AAA:"

    If TypeOf ent Is AcadBlockReference Then

        Set blk = ent

        If UCase(blk.Name) = "AAA" Then

            blk.Name = "BBB" 'The MUST be a block "BBB" defined in this drawing first

            i = i + 1

        Else

           ThsDrawing.Utility.Prompt vbCr & "Picked block is not block AAA!"

        End If

    Else

        ThisDrawing.Utility.Prompt vbCr & "Picked entity is not a block reference!"

    End If

Loop While (i < 3)


End Sub
